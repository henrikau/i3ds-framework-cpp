DepthMap-Types DEFINITIONS ::=
BEGIN
IMPORTS T-UInt32 FROM TASTE-BasicTypes
T-UInt16, T-Float FROM TASTE-ExtendedTypes;

--- Depth measurement validity adapted from SARGON.
Depth-validity-t ::=
ENUMERATED
{
   valid-measurement,
   too-far,
   too-near,
   measurement-error
}

--- Depth map with distances in meter relative to sensor.
DepthMap{T-UInt32: maxDepthMapSize} ::=
SEQUENCE
{
    distances    SEQUENCE (SIZE(1..maxDepthMapSize)) OF T-Float,
    validity     SEQUENCE (SIZE(1..maxDepthMapSize)) OF Depth-validity-t,
    map-height   T-UInt16,
    map-width    T-UInt16
}

END
