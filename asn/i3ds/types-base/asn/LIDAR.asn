--------------------------------------------------------------------------------
--- ASN.1 message definitions for the I3DS sensor suite.
---
--- Copyright (C) 2017      Stiftelsen SINTEF
--- Copyright (C) 2018      SINTEF AS
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

LIDAR-Types DEFINITIONS ::=
BEGIN
IMPORTS SampleAttributes FROM SampleAttribute-Types
PolarRegion FROM Region-Types
PointCloud FROM PointCloud-Types
T-UInt32, T-Boolean FROM TASTE-BasicTypes;

--- LIDAR region command.
LIDARRegion ::=
SEQUENCE
{
   enable   T-Boolean,
   region   PolarRegion
}

--- LIDAR configuration.
LIDARConfiguration ::=
SEQUENCE
{
   region-enabled   T-Boolean,
   region           PolarRegion
}

--- LIDAR measurement.
LIDARMeasurement{T-UInt32: maxPointCloudSize} ::=
SEQUENCE
{
   attributes   SampleAttributes,
   points       PointCloud{maxPointCloudSize},
   region       PolarRegion
}

--- LIDAR measurements for 100K, 200K, 400K sample points.
LIDARMeasurement100K ::= LIDARMeasurement{100000}
LIDARMeasurement200K ::= LIDARMeasurement{200000}
LIDARMeasurement400K ::= LIDARMeasurement{400000}

END
