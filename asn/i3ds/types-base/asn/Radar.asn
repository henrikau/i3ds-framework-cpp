--------------------------------------------------------------------------------
--- ASN.1 message definitions for the I3DS sensor suite.
---
--- Copyright (C) 2017      Stiftelsen SINTEF
--- Copyright (C) 2018      SINTEF AS
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

Radar-Types DEFINITIONS ::=
BEGIN
IMPORTS SampleAttributes FROM SampleAttribute-Types
PlanarRegion FROM Region-Types
T-UInt32, T-Boolean FROM TASTE-BasicTypes
DepthMap, DepthValidityList FROM DepthMap-Types;

--- Radar region command.
RadarRegion ::=
SEQUENCE
{
    enable   T-Boolean,
    region   PlanarRegion
}

--- Radar configuration.
RadarConfiguration ::=
SEQUENCE
{
   region-enabled   T-Boolean,
   region           RadarRegion
}

--- Radar measurement.
RadarMeasurement{T-UInt32: maxDepthMapSize} ::=
SEQUENCE
{
   attributes  SampleAttributes,
   distances   DepthMap{maxDepthMapSize},
   validity    DepthValidityList{maxDepthMapSize},
   region      RadarRegion
}

--- Radar measurements for 100K, 200K, 400K sample points.
RadarMeasurement100K ::= RadarMeasurement{100000}
RadarMeasurement200K ::= RadarMeasurement{200000}
RadarMeasurement400K ::= RadarMeasurement{400000}

END
