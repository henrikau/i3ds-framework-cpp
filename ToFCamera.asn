ToFCamera-Types DEFINITIONS ::=
BEGIN
IMPORTS StateCommand, SensorRate, ROI-t FROM SensorSuite-Types
PointCloud FROM PointCloud-Types
T-Boolean FROM TASTE-BasicTypes;

--- ToF camera command
ToFCameraCommand ::=
CHOICE
{
   set-state StateCommand,
   set-rate  SensorRate,
   set-roi   ROI-t,
   trigger   T-Boolean
}

--- ToF camera configuration
ToFCameraConfiguration ::=
CHOICE
{
   state StateCommand,
   rate  SensorRate,
   roi   ROI-t
}

--- ToF camera measurement
ToFCameraMeasurement{T-Uint32: maxPointCloudSize, T-Uint16: maxAttributes} ::=
SEQUENCE
{
    timestamp  Time,
    points     PointCloud{maxPointCloudSize},
    attributes SEQUENCE (SIZE(0..maxAttributes)) OF Sample-attribute-t,
    roi        ROI-t
}

END
