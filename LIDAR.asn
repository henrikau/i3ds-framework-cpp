LIDAR-Types DEFINITIONS ::=
BEGIN
IMPORTS StateCommand, SensorRate, ROI-t FROM SensorSuite-Types
T-Boolean FROM TASTE-BasicTypes;

--- LIDAR command
LIDARCommand ::=
CHOICE
{
   set-state  StateCommand,
   set-rate  SensorRate,
   set-roi   ROI-t,
   trigger T-Boolean
}

END
