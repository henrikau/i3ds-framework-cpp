--------------------------------------------------------------------------------
--- ASN.1 message definitions for the I3DS sensor suite.
---
--- Copyright (C) 2017      Stiftelsen SINTEF
--- Copyright (C) 2018      SINTEF AS
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

ToFCamera-Types DEFINITIONS ::=
BEGIN
IMPORTS SensorCommand, SensorConfiguration FROM SensorSuite-Types
SampleAttributes FROM SampleAttribute-Types
PlanarRegion FROM Region-Types
DepthValidityList, DepthMap FROM DepthMap-Types
T-UInt32 FROM TASTE-BasicTypes;

--- ToF command
ToFCommand ::=
CHOICE
{
   sensor-command  SensorCommand,
   set-region      PlanarRegion
}

--- ToF configuration
ToFConfiguration ::=
CHOICE
{
   config-sensor  SensorConfiguration,
   config-region  PlanarRegion
}

--- ToF measurement
ToFMeasurement{T-UInt32: maxDepthMapSize} ::=
SEQUENCE
{
   attributes  SampleAttributes,
   distances   DepthMap{maxDepthMapSize},
   validity    DepthValidityList{maxDepthMapSize},
   region      PlanarRegion
}

END
