--------------------------------------------------------------------------------
--- ASN.1 message definitions for the I3DS sensor suite.
---
--- Copyright (C) 2017      Stiftelsen SINTEF
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

DepthMap-Types DEFINITIONS ::=
BEGIN
IMPORTS T-UInt32 FROM TASTE-BasicTypes
T-UInt16, T-Float FROM TASTE-ExtendedTypes;

--- Depth measurement validity adapted from SARGON.
Depth-validity-t ::=
ENUMERATED
{
   valid-measurement,
   too-far,
   too-near,
   measurement-error
}

--- List of depth measurement validities.
DepthValidityList{T-UInt32: maxSize} ::= SEQUENCE (SIZE(1..maxSize)) OF Depth-validity-t

--- Depth map with distances in meters relative to sensor.
DepthMap{T-UInt32: maxSize} ::= SEQUENCE (SIZE(1..maxSize)) OF T-Float

END
