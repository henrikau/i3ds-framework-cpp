--------------------------------------------------------------------------------
--- ASN.1 message definitions for the I3DS sensor suite.
---
--- Copyright (C) 2017      Stiftelsen SINTEF
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

Region-Types DEFINITIONS ::=
BEGIN
IMPORTS T-UInt16, T-Float FROM TASTE-ExtendedTypes;

--------------------------------------------------------------------------------
--- Planar region definition in pixels
--------------------------------------------------------------------------------
--- Relative to upper left corner of image that is (0,0)
---
--- (0,0) -x->
---   |
---   y
---   |
---   v
--------------------------------------------------------------------------------
PlanarRegion ::=
SEQUENCE
{
    offset-x T-UInt16,
    offset-y T-UInt16,
    size-x   T-UInt16,
    size-y   T-UInt16
}

--------------------------------------------------------------------------------
--- Polar region definition in radians
--------------------------------------------------------------------------------
--- Relative to the defined center of the sensor that is (0,0)
---
--- (0,0) -x->
---   |
---   y
---   |
---   v
--------------------------------------------------------------------------------
PolarRegion ::=
SEQUENCE
{
    offset-x T-Float,
    offset-y T-Float,
    size-x   T-Float,
    size-y   T-Float
}

END
