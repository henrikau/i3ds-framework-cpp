--------------------------------------------------------------------------------
--- ASN.1 message definitions for the I3DS sensor suite.
---
--- Copyright (C) 2017      Stiftelsen SINTEF
--- Copyright (C) 2018      SINTEF AS
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

SensorSuite-Types DEFINITIONS ::=
BEGIN
IMPORTS T-UInt32 FROM TASTE-BasicTypes
T-String FROM TASTE-ExtendedTypes
Time FROM Time-Types
Temperature FROM Temperature-Types;

--------------------------------------------------------------------------------
---  State of operation for sensors and corresponding commands and _events_
--------------------------------------------------------------------------------
---
---  SENSOR      = INACTIVE,
---  INACTIVE    = (activate   -> STANDBY),
---  STANDBY     = (start      -> OPERATIONAL
---                |deactivate -> INACTIVE
---                |_failure_  -> FAILURE),
---  OPERATIONAL = (stop       -> STANDBY,
---                |_count_    -> STANDBY,
---                |_failure_  -> FAILURE),
---  FAILURE     = (_restore_  -> STANDBY
---                |deactivate -> INACTIVE).
--------------------------------------------------------------------------------
SensorState  ::= ENUMERATED {inactive, standby, operational, failure}
StateCommand ::= ENUMERATED {activate, start, stop, deactivate}

-- Sensor rate given as seconds between periodic samples (inverse of frequency).
SensorRate ::= REAL(0.0 .. 3.402823466e+38)

-- The node ID is a 24-bit integer identifying a node in the suite (such as a sensor).
NodeID ::= INTEGER(0 .. 16777215)

-- The endpoint ID is a 8-bit integer identifying the endpoint within the node.
EndpointID ::= INTEGER(0 .. 255)

-- Endpoint ID for command request (input with response).
command-Endpoint EndpointID ::= 1

-- Endpoint ID for configuration query request (input with response).
configuration-Endpoint EndpointID ::= 2

-- Endpoint ID for status (output without response).
status-Endpoint EndpointID ::= 128

-- Endpoint ID for measurements (output without response).
measurement-Endpoint EndpointID ::= 129

--  Sensor status message is common for all sensor classes.
SensorStatus ::=
SEQUENCE
{
    state        SensorState,
    temperature  Temperature,
    message      T-String
}

--- Sensor command common for all sensor classes, extended by nesting.
SensorCommand ::=
CHOICE
{
   set-state  StateCommand,    -- State change command
   set-rate   SensorRate,      -- Rate of sampling when operational.
   set-count  T-UInt32         -- Number of samples, where 0 is infinite.
}

--- Sensor configuration common for all sensor classes, extended by nesting.
SensorConfiguration ::=
SEQUENCE
{
   config-rate   SensorRate,  -- Rate of sampling when operational.
   config-count  T-UInt32     -- Number of samples, where 0 is infinite.
}

--- Request result codes.
ResultCode ::=
ENUMERATED
{
   success,            -- Successfully executed the request.
   error-node-id,      -- The node ID was not recognized.
   error-endpoint-id,  -- The endpoint ID was not recognized.
   error-state,        -- The request is illegal from current state.
   error-unsupported,  -- The request is not supported by sensor.
   error-other         -- Other error, see message.
}

--- Sensor command response common for all sensor classes.
SensorResponse ::=
SEQUENCE
{
   result   ResultCode,
   message  T-String
}

END
