--------------------------------------------------------------------------------
--- ASN.1 message definitions for the I3DS sensor suite.
---
--- Copyright (C) 2017      Stiftelsen SINTEF
--- Copyright (C) 2018      SINTEF AS
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

Camera-Types DEFINITIONS ::=
BEGIN
IMPORTS SampleAttributes FROM SampleAttribute-Types
PlanarRegion FROM Region-Types
T-UInt8, T-UInt32, T-Boolean FROM TASTE-BasicTypes
T-Float, T-UInt16 FROM TASTE-ExtendedTypes
Frame-mode-t, ImageFrame FROM Frame-Types;

--- Exposure time in microseconds
ExposureTime ::= T-UInt32

--- Sensor gain in decibel, range is camera dependent
SensorGain ::= T-Float

--- Camera exposure command.
CameraExposure ::=
SEQUENCE
{
    exposure   ExposureTime,
    gain       SensorGain
}

--- Camera auto exposure command.
CameraAutoExposure ::=
SEQUENCE
{
    enable         T-Boolean,
    max-exposure   ExposureTime,
    max-gain       SensorGain
}

--- Flash strength from 0 (off) to 255 (full)
FlashStrength ::= T-UInt8

--- Camera flash illumination command.
CameraFlash ::=
SEQUENCE
{
    enable     T-Boolean,
    strength   FlashStrength
}

--- Camera region command.
CameraRegion ::=
SEQUENCE
{
    enable   T-Boolean,
    region   PlanarRegion
}

--- Illumination pattern sequence, range depends on camera
PatternSequence ::= T-UInt16

--- Illumination pattern ID, 0 is none, range depends on camera
PatternID ::= T-UInt16

--- Camera pattern illumination command.
CameraPattern ::=
SEQUENCE
{
    enable     T-Boolean,
    sequence   PatternSequence
}

--- Camera configuration.
CameraConfiguration ::=
SEQUENCE
{
   exposure                ExposureTime,
   gain                    SensorGain,
   auto-exposure-enabled   T-Boolean,
   max-exposure            ExposureTime,
   max-gain                SensorGain,
   region-enabled          T-Boolean,
   region                  PlanarRegion,
   flash-enabled           T-Boolean,
   flash-strength          FlashStrength,
   pattern-enabled         T-Boolean,
   pattern-sequence        PatternSequence
}

--- Camera measurement
CameraMeasurement{T-UInt32: maxImageBytes} ::=
SEQUENCE
{
   attributes  SampleAttributes,
   image       ImageFrame{maxImageBytes},
   frame-mode  Frame-mode-t,
   data-depth  T-UInt8,
   pixel-size  T-UInt8,
   region      PlanarRegion,
   pattern     PatternID
}

--- Camera measurements for 1 MiB, 4 MiB and 8 MiB images.
CameraMeasurement1M ::= CameraMeasurement{1048576}
CameraMeasurement4M ::= CameraMeasurement{4194304}
CameraMeasurement8M ::= CameraMeasurement{8388608}

--- Stereo camera measurement
StereoCameraMeasurement{T-UInt32: maxImageBytes} ::=
SEQUENCE
{
   attributes   SampleAttributes,
   image-left   ImageFrame{maxImageBytes},
   image-right  ImageFrame{maxImageBytes},
   frame-mode   Frame-mode-t,
   data-depth   T-UInt8,
   pixel-size   T-UInt8,
   region       PlanarRegion
}

--- Stereo camera measurements for 4 MiB and 8 MiB left/right images.
StereoCameraMeasurement4M ::= StereoCameraMeasurement{4194304}
StereoCameraMeasurement8M ::= StereoCameraMeasurement{8388608}

END
