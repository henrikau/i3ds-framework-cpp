--------------------------------------------------------------------------------
--- ASN.1 message definitions for the I3DS sensor suite.
---
--- Copyright (C) 2017      Stiftelsen SINTEF
--- Copyright (C) 2018      SINTEF AS
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

SampleAttribute-Types DEFINITIONS ::=
BEGIN
IMPORTS T-UInt8, T-Boolean FROM TASTE-BasicTypes
T-Int64, T-Double, T-String FROM TASTE-ExtendedTypes
Time FROM Time-Types;

--- Sample validity
SampleValidity ::=
ENUMERATED
{
   sample-empty,
   sample-valid,
   sample-invalid
}

--- Short string for attributes
T-String16 ::= OCTET STRING (SIZE(0..16))

--- Sample attribute value
Attribute-value-t ::=
CHOICE
{
   boolean-value    T-Boolean,
   discrete-value   T-Int64,
   real-value       T-Double,
   string-value     T-String16
}

--- Sample attribute name/value pair
Sample-attribute-t ::=
SEQUENCE
{
   attribute-key     T-UInt8,
   attribute-value   Attribute-value-t
}

--- Sample attributes common for all measurements.
SampleAttributes ::=
SEQUENCE
{
   timestamp   Time,
   validity    SampleValidity,
   attributes  SEQUENCE (SIZE(0..5)) OF Sample-attribute-t
}

END
