--------------------------------------------------------------------------------
--- ASN.1 message definitions for the I3DS sensor suite.
---
--- Copyright (C) 2017      Stiftelsen SINTEF
--- Copyright (C) 2018      SINTEF AS
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

Frame-Types DEFINITIONS ::=
BEGIN
IMPORTS SampleAttributes FROM SampleAttribute-Types
PlanarRegion FROM Region-Types
T-UInt32 FROM TASTE-BasicTypes
T-UInt16 FROM TASTE-ExtendedTypes;

--- Legal frame modes adapted from SARGON
Frame-mode-t ::=
ENUMERATED
{
   mode-undefined,
   mode-mono,       -- Grayscale image
   mode-rgb,        -- Colour image in RGB format
   mode-bgr,        -- Colour image in BGR format
   mode-uyvy,       -- Colour image in UYVY format
   mode-rgba,       -- Colour image in RGBA format (RGB32)
   mode-bayer-rggb, -- RAW image with RGGB bayer layout
   mode-bayer-grbg, -- RAW image with GRBG bayer layout
   mode-bayer-bggr, -- RAW image with BGGR bayer layout
   mode-bayer-gbrg, -- RAW image with GBRG bayer layout
   mode-pjpg,       -- Compressed image in PJPG format
   mode-jpeg,       -- Compressed image in JPEG format
   mode-png,        -- Compressed image in PNG format
   mode-tiff        -- Image in TIFF format
}

--- Image frame is an octet string
ImageFrame{T-UInt32: maxImageBytes} ::= OCTET STRING (SIZE(0..maxImageBytes))

--- Mono camera frame measurement
MonoFrame{T-UInt32: maxImageBytes} ::=
SEQUENCE
{
   attributes  SampleAttributes,
   image       ImageFrame{maxImageBytes},
   frame-mode  Frame-mode-t,
   data-depth  T-UInt8,
   pixel-size  T-UInt8,
   region      PlanarRegion
}

--- Stereo camera frame measurement
StereoFrame{T-UInt32: maxImageBytes} ::=
SEQUENCE
{
   attributes   SampleAttributes,
   image-left   ImageFrame{maxImageBytes},
   image-right  ImageFrame{maxImageBytes},
   frame-mode   Frame-mode-t,
   data-depth   T-UInt8,
   pixel-size   T-UInt8,
   region       PlanarRegion
}

--- Pre-defined frames of different single image size (in MiB).
MonoFrame1M ::= MonoFrame{1048576}
MonoFrame4M ::= MonoFrame{4194304}
MonoFrame8M ::= MonoFrame{8388608}
StereoFrame4M ::= StereoFrame{4194304}
StereoFrame8M ::= StereoFrame{8388608}

END
