--------------------------------------------------------------------------------
--- ASN.1 message definitions for the I3DS sensor suite.
---
--- Copyright (C) 2017      Stiftelsen SINTEF
--- Copyright (C) 2018      SINTEF AS
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

Basler-HRCamera-Types DEFINITIONS ::=
BEGIN
IMPORTS CameraMeasurement FROM Camera-Types
T-UInt32 FROM TASTE-BasicTypes
T-UInt16 FROM TASTE-ExtendedTypes;

--- Basler HR camera is 16 bits * 2048 * 2048 = 8388608 Bytes = 8 MiB
basler-HRImageWidth  T-UInt16 ::= 2048
basler-HRImageHeight T-UInt16 ::= 2048
basler-HRDataDepth   T-UInt16 ::= 12
basler-HRPixelSize   T-UInt16 ::= 2
basler-HRImageSize   T-UInt32 ::= 8388608

--- Basler HR camera measurement
Basler-HRCameraMeasurement ::= CameraMeasurement{basler-HRImageSize}

END
