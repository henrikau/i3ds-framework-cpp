--------------------------------------------------------------------------------
--- ASN.1 message definitions for the I3DS sensor suite.
---
--- Copyright (C) 2017      Stiftelsen SINTEF
--- Copyright (C) 2018      SINTEF AS
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

Hertz-Radar-Types DEFINITIONS ::=
BEGIN
IMPORTS RadarMeasurement FROM Radar-Types
T-UInt32 FROM TASTE-BasicTypes;

--- Hertz HF radar depthmap is 121 * 121 = 14641
hertz-RadarDepthMapWidth  T-UInt32 ::= 121
hertz-RadarDepthMapHeight T-UInt32 ::= 121
hertz-RadarResolution     T-UInt32 ::= 14641

--- Hertz HF radar measurement
Hertz-RadarMeasurement ::= RadarMeasurement{hertz-RadarResolution}

END
