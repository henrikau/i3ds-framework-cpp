--------------------------------------------------------------------------------
--- ASN.1 message definitions for the I3DS sensor suite.
---
--- Copyright (C) 2017      Stiftelsen SINTEF
--- Copyright (C) 2018      SINTEF AS
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

Beamagine-LIDAR-Types DEFINITIONS ::=
BEGIN
IMPORTS LIDARMeasurement FROM LIDAR-Types
T-UInt32 FROM TASTE-BasicTypes
T-UInt16 FROM TASTE-ExtendedTypes;

--- Beamagine LIDAR resolution point cloud is at most 400 * 400 = 160,000
beamagine-LIDARWidth      T-UInt16 ::= 400
beamagine-LIDARHeight     T-UInt16 ::= 400
beamagine-LIDARResolution T-UInt32 ::= 160000

--- Beamagine LIDAR measurement
Beamagine-LIDARMeasurement ::= LIDARMeasurement{beamagine-LIDARResolution}

END
