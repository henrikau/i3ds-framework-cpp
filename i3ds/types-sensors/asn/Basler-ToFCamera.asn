--------------------------------------------------------------------------------
--- ASN.1 message definitions for the I3DS sensor suite.
---
--- Copyright (C) 2017      Stiftelsen SINTEF
--- Copyright (C) 2018      SINTEF AS
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

Basler-ToFCamera-Types DEFINITIONS ::=
BEGIN
IMPORTS ToFMeasurement FROM ToFCamera-Types
T-UInt32 FROM TASTE-BasicTypes;

--- Basler ToF point cloud is at most 640 * 480 = 307200
basler-ToFResolution T-UInt32 ::= 307200

--- Basler ToF measurement
Basler-ToFMeasurement ::= ToFMeasurement{basler-ToFResolution}

END
